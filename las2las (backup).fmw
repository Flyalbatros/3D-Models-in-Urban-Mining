FME workspace las2las (backup).fmw

Parameters:
- DestDataset_LAS = C:\Users\P.A. Ruben\Desktop\Master thesis\05 - trial data   # Destination ASPRS LAS Folder
- SourceDataset_LAS = C:\Users\P.A. Ruben\Desktop\Master thesis\05 - trial data\C_37HN1.LAZ   # Source ASPRS LAS File(s)
- SourceDataset_LAS_7 = C:\Users\P.A. Ruben\Desktop\Master thesis\05 - trial data\C_37HN1.LAZ   # Source ASPRS LAS File(s)
- SourceDataset_LAS_9 = C:\Users\P.A. Ruben\Desktop\Master thesis\05 - trial data\C_37HN1.LAZ   # Source ASPRS LAS File(s)
- SourceDataset_LAS_5 = C:\Users\P.A. Ruben\Desktop\Master thesis\05 - trial data\C_37HN1.LAZ   # Source ASPRS LAS File(s)
- SourceDataset_LAS_8 = C:\Users\P.A. Ruben\Desktop\Master thesis\05 - trial data\C_37HN1.LAZ   # Source ASPRS LAS File(s)

Readers:
- LAS_1: LAS from $(SourceDataset_LAS) in EPSG:28992
- LAS_2: LAS from $(SourceDataset_LAS_5) in EPSG:28992
- LAS_3: LAS from $(SourceDataset_LAS_7) in EPSG:28992
- LAS_4: LAS from $(SourceDataset_LAS_9) in EPSG:28992
- LAS_6: LAS from $(SourceDataset_LAS_8) in EPSG:28992

Writers:
- LAS_5: LAS to $(DestDataset_LAS)

LAS (reader LAS_1) [off]
LAS (reader LAS_2) [off]
LAS (reader LAS_3) [off]
LAS (reader LAS_4) [off]
    -> PointCloudThinner
PointCloudThinner [off]
    INTERVAL = 1
    THINNED -> PointCloudSplitter
PointCloudSplitter [off]
    OUTPUT_ATTR = _split_value
    SPLIT_BY_DISPLAY = classification
    SPLIT_TYPE = Unique
    SPLIT -> Tester
    SPLIT -> Tester_2
Tester [off]
    BOOL_OP = OR
    TEST_CLAUSE = TEST @Value(_split_value) = 6
    PASSED -> waalhaven_zuid_bldg (writer LAS_5)
waalhaven_zuid_bldg (writer LAS_5) [off]
Tester_2 [off]
    BOOL_OP = OR
    TEST_CLAUSE = TEST @Value(_split_value) = 1
    PASSED -> waalhaven_zuid_nc (writer LAS_5)
waalhaven_zuid_nc (writer LAS_5) [off]
LAS (reader LAS_6)
    -> kerk (writer LAS_5)
kerk (writer LAS_5)
